module foundation {
  namespace "http://com/example/foundation";
  prefix foundation;

  import ietf-inet-types {
    prefix inet;
  }
  import tailf-common {
    prefix tailf;
  }
  import tailf-ncs {
    prefix ncs;
  }

  //link节点信息用于link_service
  grouping node{
    leaf device{
      type leafref{
        path "/ncs:devices/ncs:device/ncs:name";
      }
    }
    container interface{
      leaf int_type{
        type enumeration{
          enum FastEthernet;
          enum GigabitEthernet;
          enum TenGigE;
          enum Ethernet;
        }
      }
      leaf int_id{
        type string;
      }
    }
  }

  augment /ncs:services {
    list foundation
    {
      key foun_name;
      leaf foun_name{
        type string;
      }
      container link_service{
        list link_part{

          uses ncs:service-data;
          ncs:servicepoint "link_service-servicepoint";

          key part_name;
          leaf part_name{
            type string;
          }
          //需要输入该part中将会有多少个link，用于计算网络地址和掩码。
          leaf link_num{
            type uint32;
          }
          container netblock{
            //所有link所公用的一个网段
            leaf netaddress{
              type inet:ipv4-address;
              default "10.1.0.0";
            }
            leaf netmask{
              type string;
              default "16";
            }
          }
          list link{
            key "link_id";
            leaf link_id{
              type uint16;
            }
            container s_node{
              uses node;
            }
            container d_node{
              uses node;
            }

          }
        }
      }

      container IGP_service{
        container OSPF{
          list process{

            uses ncs:service-data;
            ncs:servicepoint "IGP_service-servicepoint";

            key "process_id";
            leaf process_id{type string;}
            container route_import{
              leaf route_type{
                type enumeration{
                  enum static;
                  enum ospf;
                  enum bgp;
                  enum isis;
                  enum none;
                }
              }
              leaf red_process_id{type uint32;}
              leaf metric_type{
                type enumeration{
                  enum type-one;
                  enum type-two;
                }
              }
              leaf metric_value{type uint32;}
            }
            container areas{
              list area{
                key "area_id";
                leaf area_id{type uint32;}
                leaf area_type{
                  type enumeration{
                    enum normal;
                    enum stub;
                    enum nssa;
                  }
                }
                leaf totally{
                  type enumeration{
                    enum TRUE;
                    enum FALSE;
                  }
                }
                container devices{
                  list device{
                    key "device_id";
                    leaf device_id{type string;}
                    leaf router_id{type string;}
                    container interfaces{
                      list interface{
                        key "int_type int_id";
                        leaf int_type{type string;}
                        leaf int_id{type string;}
                        leaf network_type{
                          type enumeration{
                            enum broadcast;
                            enum non-broadcast;
                            enum point-to-point;
                            enum point-to-multipoint;
                          }
                        }
                      }
                    }
                  }
                }
              }
            }
          }
        }
      }
    }
  }
}
